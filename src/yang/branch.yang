module branch {

  namespace "http://example.com/branch";
  prefix branch;

  import pnp-device { prefix pnp-device; }

  import ietf-inet-types { prefix inet; }
  import tailf-common { prefix tailf; }
  import tailf-ncs { prefix ncs; }

  description
    "Branch Configuration Module";

  revision 2019-07-09 {
    description
      "Initial revision.";
  }

  list branch {
    description "Branch Configuration Service";

    key name;
    leaf name {
      tailf:info "Branch Name";
      type string;
    }

    uses ncs:service-data;
    ncs:servicepoint branch-servicepoint;

    list device {
      key name;
      uses pnp-device:pnp-device-grouping;
    }

  }
}
